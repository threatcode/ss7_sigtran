-- $Id: MAP-OperationAndMaintenanceOperations.asn 34814 2010-11-08 23:15:16Z etxrab $
-- 3GPP TS 29.002 V9.3.0 (2010-09) 
--17.6.2	Operation and Maintenance Operations
MAP-OperationAndMaintenanceOperations {
   itu-t identified-organization (4) etsi (0) mobileDomain (0)
   gsm-Network (1) modules (3) map-OperationAndMaintenanceOperations (6)
   version12 (12)}

DEFINITIONS

::=

BEGIN

EXPORTS
	activateTraceModeV2,
	activateTraceModeV3,
	deactivateTraceModeV2,
	deactivateTraceModeV3,
	sendIMSI
;

IMPORTS
	OPERATION
FROM Remote-Operations-Information-Objects {
joint-iso-itu-t remote-operations(4)
  informationObjects(5) version1(0)}

	systemFailure,
	dataMissing,
	unexpectedDataValue,
	facilityNotSupported,
	unknownSubscriber,
	unidentifiedSubscriber,
	tracingBufferFull
FROM MAP-Errors {
   itu-t identified-organization (4) etsi (0) mobileDomain (0)
   gsm-Network (1) modules (3) map-Errors (10) version12 (12)}

	ActivateTraceModeArgV2,
	ActivateTraceModeArgV3,
	ActivateTraceModeResV3,
	DeactivateTraceModeArgV2,
	DeactivateTraceModeArgV3,
	DeactivateTraceModeResV3
FROM MAP-OM-DataTypes {
   itu-t identified-organization (4) etsi (0) mobileDomain (0)
   gsm-Network (1) modules (3) map-OM-DataTypes (12) version12 (12)}

	ISDN-AddressString,
	IMSI
FROM MAP-CommonDataTypes {
   itu-t identified-organization (4) etsi (0) mobileDomain (0)
   gsm-Network (1) modules (3) map-CommonDataTypes (18) version12 (12)}
;


activateTraceModeV2  OPERATION ::= {				--Timer m
	ARGUMENT
		ActivateTraceModeArgV2
	ERRORS {
		systemFailure |
		dataMissing |
		unexpectedDataValue |
		facilityNotSupported |
		unidentifiedSubscriber |
		tracingBufferFull}
	CODE	local:50 }

activateTraceModeV3  OPERATION ::= {				--Timer m
	ARGUMENT
		ActivateTraceModeArgV3
	RESULT
		ActivateTraceModeResV3
		-- optional
	ERRORS {
		systemFailure |
		dataMissing |
		unexpectedDataValue |
		facilityNotSupported |
		unidentifiedSubscriber |
		tracingBufferFull}
	CODE	local:50 }

deactivateTraceModeV2  OPERATION ::= {				--Timer m
	ARGUMENT
		DeactivateTraceModeArgV2
	ERRORS {
		systemFailure |
		dataMissing |
		unexpectedDataValue |
		facilityNotSupported |
		unidentifiedSubscriber}
	CODE	local:51 }

deactivateTraceModeV3  OPERATION ::= {				--Timer m
	ARGUMENT
		DeactivateTraceModeArgV3
	RESULT
		DeactivateTraceModeResV3
		-- optional
	ERRORS {
		systemFailure |
		dataMissing |
		unexpectedDataValue |
		facilityNotSupported |
		unidentifiedSubscriber}
	CODE	local:51 }

sendIMSI  OPERATION ::= {				--Timer m
	ARGUMENT
		ISDN-AddressString
	RESULT
		IMSI
	ERRORS {
		dataMissing |
		unexpectedDataValue |
		unknownSubscriber}
	CODE	local:58 }

END
