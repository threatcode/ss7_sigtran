-- $Id: MAP-Protocol.asn 34814 2010-11-08 23:15:16Z etxrab $
-- 3GPP TS 29.002 V9.3.0 (2010-09)
--17.5	MAP operation and error codes
MAP-Protocol {
   itu-t identified-organization (4) etsi (0) mobileDomain (0)
   gsm-Network (1) modules (3) map-Protocol (4) version12 (12)}

DEFINITIONS

::=

BEGIN

IMPORTS
OPERATION
FROM Remote-Operations-Information-Objects {
joint-iso-itu-t remote-operations(4) informationObjects(5) version1(0)}

	updateLocation,
	cancelLocationV2,
	cancelLocationV3,
	purgeMSV2,
	purgeMSV3,
	sendIdentificationV2,
	sendIdentificationV3,
	updateGprsLocation,
	prepareHandoverV2,
	prepareHandoverV3,
	sendEndSignalV2,
	sendEndSignalV3,
	processAccessSignallingV2,
	processAccessSignallingV3,
	forwardAccessSignallingV2,
	processAccessSignallingV3,
	prepareSubsequentHandoverV2,
	prepareSubsequentHandoverV3,
	sendAuthenticationInfoV2,
	sendAuthenticationInfoV3,
	authenticationFailureReport,
	checkIMEIV2,
	checkIMEIV3,
	insertSubscriberDataV2,
	insertSubscriberDataV3,
	deleteSubscriberDataV2,
	deleteSubscriberDataV3,
	reset,
	forwardCheckSS-Indication,
	restoreData,
	provideSubscriberInfo,
	anyTimeInterrogation,
	anyTimeSubscriptionInterrogation,
	anyTimeModification,
	sendRoutingInfoForGprs,
	failureReport,
	noteMsPresentForGprs,
	noteMM-Event,
	noteSubscriberDataModified


FROM MAP-MobileServiceOperations {
   itu-t identified-organization (4) etsi (0) mobileDomain (0)
   gsm-Network (1) modules (3) map-MobileServiceOperations (5)
   version12 (12)}

	activateTraceModeV2,
	activateTraceModeV3,
	deactivateTraceModeV2,
	deactivateTraceModeV3,
	sendIMSI
FROM MAP-OperationAndMaintenanceOperations {
   itu-t identified-organization (4) etsi (0) mobileDomain (0)
   gsm-Network (1) modules (3) map-OperationAndMaintenanceOperations (6)
   version12 (12)}

	sendRoutingInfoV2,
	sendRoutingInfoV3,
	provideRoamingNumberV2,
	provideRoamingNumberV3,
	resumeCallHandlingV3,
	resumeCallHandlingV4,
	provideSIWFSNumber,
	sIWFSSignallingModify,
	setReportingState,
	statusReport,
	remoteUserFree,
	ist-Alert,
	ist-Command,
	releaseResources
FROM MAP-CallHandlingOperations {
   itu-t identified-organization (4) etsi (0) mobileDomain (0)
   gsm-Network (1) modules (3) map-CallHandlingOperations (7)
   version12 (12)}

	registerSS,
	eraseSS,
	activateSS,
	deactivateSS,
	interrogateSS,
	processUnstructuredSS-Request,
	unstructuredSS-Request,
	unstructuredSS-Notify,
	registerPassword,
	getPassword,
	ss-InvocationNotification,
	registerCC-Entry,
	eraseCC-Entry
FROM MAP-SupplementaryServiceOperations {
   itu-t identified-organization (4) etsi (0) mobileDomain (0)
   gsm-Network (1) modules (3) map-SupplementaryServiceOperations (8)
   version12 (12)}

	sendRoutingInfoForSMV2,
	sendRoutingInfoForSMV3,
	mo-ForwardSM,
	mt-ForwardSM,
	reportSM-DeliveryStatusV2,
	reportSM-DeliveryStatusV3,
	alertServiceCentre,
	-- Add Older version [HW]
	alertServiceCentreWithoutResult,
	noteSubscriberPresent,
	-- End [HW]
	informServiceCentreV2,
	informServiceCentreV3,
	readyForSMV2,
	readyForSMV3,
	mt-ForwardSM-VGCS
FROM MAP-ShortMessageServiceOperations {
   itu-t identified-organization (4) etsi (0) mobileDomain (0)
   gsm-Network (1) modules (3) map-ShortMessageServiceOperations (9)
   version12 (12)}

	prepareGroupCall,
	processGroupCallSignalling,
	forwardGroupCallSignalling,
	sendGroupCallEndSignal,
	sendGroupCallInfo
FROM MAP-Group-Call-Operations {
   itu-t identified-organization (4) etsi (0) mobileDomain (0)
   gsm-Network (1) modules (3) map-Group-Call-Operations (22)
   version12 (12)}

	provideSubscriberLocation,
	sendRoutingInfoForLCS,
	subscriberLocationReport
FROM MAP-LocationServiceOperations {
   itu-t identified-organization (4) etsi (0) mobileDomain (0)
   gsm-Network (1) modules (3) map-LocationServiceOperations (24)
   version12 (12)}


;
Supported-MAP-Operations OPERATION ::= {updateLocation | cancelLocationV2 |
cancelLocationV3 | purgeMSV2 | purgeMSV3 |
sendIdentificationV2 | sendIdentificationV3 | updateGprsLocation |
prepareHandoverV2 | sendEndSignalV2 | processAccessSignallingV2 |
forwardAccessSignallingV2 | prepareSubsequentHandoverV2 |
prepareHandoverV3 | sendEndSignalV3 | processAccessSignallingV3 |
forwardAccessSignallingV3 | prepareSubsequentHandoverV3 |
sendAuthenticationInfoV2 | sendAuthenticationInfoV3 | authenticationFailureReport |
checkIMEIV2 | checkIMEIV3 |
insertSubscriberDataV2 | insertSubscriberDataV3 |
deleteSubscriberDataV2 | deleteSubscriberDataV3 |
reset | forwardCheckSS-Indication | restoreData | provideSubscriberInfo |
anyTimeInterrogation | anyTimeSubscriptionInterrogation | anyTimeModification |
sendRoutingInfoForGprs | failureReport |noteMsPresentForGprs | noteMM-Event |
noteSubscriberDataModified |
activateTraceModeV2 | deactivateTraceModeV2 |
activateTraceModeV3 | deactivateTraceModeV3 |
sendIMSI |
sendRoutingInfoV2 |sendRoutingInfoV3 |
provideRoamingNumberV2 | provideRoamingNumberV3 |
resumeCallHandlingV3 | resumeCallHandlingV4 | setReportingState | statusReport |
remoteUserFree | ist-Alert |
ist-Command | registerSS | eraseSS | activateSS | deactivateSS | interrogateSS |
processUnstructuredSS-Request | unstructuredSS-Request | unstructuredSS-Notify | 
registerPassword | getPassword | ss-InvocationNotification | registerCC-Entry | eraseCC-Entry | 
sendRoutingInfoForSMV2 |reportSM-DeliveryStatusV2 | informServiceCentreV2 |
sendRoutingInfoForSMV3 |reportSM-DeliveryStatusV3 | informServiceCentreV3 |
mo-ForwardSM | mt-ForwardSM |
alertServiceCentre | readyForSMV2 | readyForSMV3 | prepareGroupCall | 
processGroupCallSignalling | forwardGroupCallSignalling | sendGroupCallEndSignal |
provideSubscriberLocation | sendRoutingInfoForLCS | subscriberLocationReport | 
releaseResources | mt-ForwardSM-VGCS | sendGroupCallInfo
-- Add SS-Operations [HW]
| processUnstructuredSS-Data | notifySS | forwardChargeAdvice | forwardCUG-Info
| buildMPTY | holdMPTY | retrieveMPTY | splitMPTY | explicitCT
| accessRegisterCCEntry | callDeflection | userUserService

| lcs-LocationNotification | lcs-MOLR | lcs-AreaEventRequest | lcs-AreaEventReport
| lcs-AreaEventCancellation | lcs-PeriodicLocationRequest | lcs-LocationUpdate
| lcs-PeriodicLocationCancellation

| noteSubscriberPresent | alertServiceCentreWithoutResult
| provideSIWFSNumber | sIWFSSignallingModify
-- End [HW]
}



-- The following operation codes are reserved for operations
-- existing in previous versions of the protocol

-- Operation Name	AC used	Oper. Code
-- 
-- sendParameters	map-ac infoRetrieval (14) version1 (1)	local:9
-- processUnstructuredSS-Data	map-ac networkFunctionalSs (18) version1 (1)	local:19
-- performHandover	map-ac handoverControl (11) version1 (1)	local:28
-- performSubsequentHandover	map-ac handoverControl (11) version1 (1)	local:30
-- noteInternalHandover	map-ac handoverControl (11) version1 (1)	local:35
-- noteSubscriberPresent	map-ac mwdMngt (24) version1 (1)	local:48
-- alertServiceCentreWithoutResult	map-ac shortMsgAlert (23) version1 (1)	local:49
-- traceSubscriberActivity	map-ac handoverControl (11) version1 (1)	local:52
-- beginSubscriberActivity	map-ac networkFunctionalSs (18) version1 (1)	local:54

-- The following error codes are reserved for errors
-- existing in previous versions of the protocol

-- Error Name	AC used	Error Code
-- 
-- unknownBaseStation	map-ac handoverControl (11) version1 (1)	local:2
-- invalidTargetBaseStation	map-ac handoverControl (11) version1 (1)	local:23
-- noRadioResourceAvailable	map-ac handoverControl (11) version1 (1)	local:24


END
